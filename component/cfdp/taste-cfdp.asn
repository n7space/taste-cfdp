TASTE-CFDP-DATAVIEW DEFINITIONS ::=
BEGIN

   APP-MARKER-CFDP-CONFIG-DATA ::= INTEGER (0 .. 4294967294)

   APP-MARKER-CFDP-ENTITY-ID ::= INTEGER (0 .. 4294967294)

   APP-MARKER-CFDP-INACTIVITY-TIMEOUT ::= INTEGER (0 .. 4294967294)

   APP-MARKER-BOOLEAN ::= BOOLEAN

   APP-MARKER-FILE-PATH ::= SEQUENCE { field-data IA5String (SIZE(0..32)) }

   APP-MARKER-OPERATION-ID ::= INTEGER (0 .. 4294967294)

   APP-MARKER-CFDP-DATA ::= SEQUENCE { field-data OCTET STRING (SIZE(0..512)) }

   APP-MARKER-CFDP-TIMEOUT ::= INTEGER (0 .. 4294967294)

   APP-MARKER-CFDP-OFFSET ::= INTEGER (0 .. 4294967294)

   APP-MARKER-CFDP-SIZE ::= INTEGER (0 .. 4294967294)

   APP-MARKER-CFDP-CHECKSUM-TYPE ::= ENUMERATED {
        modular (0),
        none(15)
   }

   APP-MARKER-CFDP-CHECKSUM ::= INTEGER (0 .. 4294967294)

   APP-MARKER-CFDP-INDICATION-TYPE ::= INTEGER (0 .. 4294967294)

   APP-MARKER-CFDP-ERROR-CODE ::= INTEGER (0 .. 4294967294)

   APP-MARKER-CFDP-ERROR-TYPE ::= INTEGER (0 .. 4294967294)

   APP-MARKER-CFDP-TRANSACTION-ID ::= SEQUENCE {
      source-entity-id INTEGER (0 .. 4294967294),
      seq-number INTEGER (0 .. 4294967294)
   }

END
