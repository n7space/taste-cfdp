TASTE-CFDP-DATAVIEW DEFINITIONS ::=
BEGIN

   CFDP-CONFIG-DATA ::= INTEGER (0 .. 4294967294)

   CFDP-ENTITY-ID ::= INTEGER (0 .. 4294967294)

   CFDP-INACTIVITY-TIMEOUT ::= INTEGER (0 .. 4294967294)

   CFDP-BOOLEAN ::= BOOLEAN

   CFDP-FILE-PATH ::= SEQUENCE { field-data IA5String (SIZE(0..32)) }

   CFDP-OPERATION-ID ::= INTEGER (0 .. 4294967294)

   CFDP-DATA ::= SEQUENCE { field-data OCTET STRING (SIZE(0..512)) }

   CFDP-TIMEOUT ::= INTEGER (0 .. 4294967294)

   CFDP-OFFSET ::= INTEGER (0 .. 4294967294)

   CFDP-SIZE ::= INTEGER (0 .. 4294967294)

   CFDP-CHECKSUM-TYPE ::= ENUMERATED {
        modular (0),
        none(15)
   }

   CFDP-CHECKSUM ::= INTEGER (0 .. 4294967294)

   CFDP-INDICATION-TYPE ::= INTEGER (0 .. 4294967294)

   CFDP-ERROR-CODE ::= INTEGER (0 .. 4294967294)

   CFDP-ERROR-TYPE ::= INTEGER (0 .. 4294967294)

   CFDP-TRANSACTION-ID ::= SEQUENCE {
      source-entity-id INTEGER (0 .. 4294967294),
      seq-number INTEGER (0 .. 4294967294)
   }

END
