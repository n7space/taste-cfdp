MEMORYACCESS-DATAVIEW DEFINITIONS ::=
BEGIN

   MemoryAccess-Address ::= INTEGER(0..4294967295)

   MemoryAccess-Size ::= INTEGER(0..4294967295)

   MemoryAccess-Data ::= OCTET STRING (SIZE (1..1024))

   MemoryAccess-Result ::= BOOLEAN

END
