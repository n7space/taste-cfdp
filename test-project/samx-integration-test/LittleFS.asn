LittleFS DEFINITIONS ::= BEGIN

MEMORY-BLOCK-INDEX ::= INTEGER (0 .. 4294967294)
MEMORY-OFFSET ::= INTEGER (0 .. 4294967294)
MEMORY-SIZE ::= INTEGER (0 .. 4294967294)
MEMORY-DATA ::= OCTET STRING (SIZE (1..255))

LITTLE-FS-INTEGER ::= INTEGER (0 .. 4294967294)

LITTLE-FS-BOOLEAN ::= BOOLEAN

LITTLE-FS-REPOSITORY-PATH ::= SEQUENCE { field-data IA5String (SIZE(0..8)) }

LITTLE-FS-FILE-NAME ::= SEQUENCE { field-data IA5String (SIZE(0..32)) }

LITTLE-FS-FILE-PATH ::= SEQUENCE {
    repository-path LITTLE-FS-REPOSITORY-PATH,
    file-name LITTLE-FS-FILE-NAME
}

LITTLE-FS-MAXIMUM-SIZE ::= INTEGER (0..255)

LITTLE-FS-ADDITIONAL-FILE-ATTRIBUTE ::= SEQUENCE { field-data OCTET STRING (SIZE(1..8)) }

LITTLE-FS-EMPTY ::= SEQUENCE {}

LITTLE-FS-FILE-NAME-LENGTH ::= INTEGER (0..32)

LITTLE-FS-MEMORY-BASE ::= CHOICE {
     ram-memory LITTLE-FS-EMPTY,
     fs-memory LITTLE-FS-FILE-NAME
}

LITTLE-FS-MEMORY-OFFSET ::= INTEGER (0..65535)

LITTLE-FS-MEMORY-DATA ::= SEQUENCE { field-data OCTET STRING (SIZE(0..128)) }

LITTLE-FS-OBJECT-TYPE ::= ENUMERATED {
     file (0),
     directory (1)
}

LITTLE-FS-OBJECT-NAME ::= SEQUENCE { field-data IA5String (SIZE(0..8)) }

LITTLE-FS-REPOSITORY-OBJECT ::= SEQUENCE {
     object-type LITTLE-FS-OBJECT-TYPE,
     object-name LITTLE-FS-OBJECT-NAME
}

LITTLE-FS-REPOSITORY-OBJECTS ::= SEQUENCE { field-data SEQUENCE (SIZE(0..64)) OF LITTLE-FS-REPOSITORY-OBJECT }

END
